Call-Diversion-Operations
{
  itu-t recommendation h 450 3 version1(0) call-diversion-operations(0)
}

DEFINITIONS AUTOMATIC TAGS ::=
BEGIN

  IMPORTS Extension FROM H4501 -- Manufacturer-specific-service-extension-definition
  { 
    itu-t recommendation h 450 1 version1(0) msi-definition(18)
  }

  H225InformationElement FROM H225-generic-parameters-definition
  {
    itu-t recommendation h 450 1 version1(0) h225-generic-parameters(6)
  }

  NonStandardParameter FROM H225 -- H323-MESSAGES see H.225.0

  EndpointAddress, PartySubaddress, PresentationAllowedIndicator FROM H4501 -- Addressing-Data-Elements 
  {
    itu-t recommendation h 450 1 version1(0) addressing-data-elements (9)
  }

  userNotSubscribed, notAvailable, invalidServedUserNumber,
  basicServiceNotProvided, resourceUnavailable, 
  supplementaryServiceInteractionNotAllowed FROM  H4501-General-Error-List
  {
    itu-t recommendation h 450 1 version1(0) general-error-list (1)
  };


  H323CallDiversionOperations ::= ENUMERATED 
  {
    activateDiversionQ(15),
    deactivateDiversionQ(16),
    interrogateDiversionQ(17),
    checkRestriction(18),
    callRerouting(19),
    divertingLegInformation1(20),
    divertingLegInformation2(21),
    divertingLegInformation3(22),
    divertingLegInformation4(100),
    cfnrDivertedLegFailed(23)
  }

  -- Definitions of general used data types:

  DiversionReason ::= ENUMERATED
  { 
    unknown(0),
    cfu(1),
    cfb(2),
    cfnr(3), 
    ...
  }

  -- The value unknown is only used if received from another network when interworking.
  IntResultList ::= SET SIZE (0..29) OF IntResult

  IntResult ::= SEQUENCE
  {
    servedUserNr      EndpointAddress,
    basicService      BasicService,
    procedure         Procedure,
    divertedToAddress EndpointAddress,
    remoteEnabled     BOOLEAN DEFAULT FALSE,
    extension         CHOICE 
    {
      extensionSeq    ExtensionSeq,
      nonStandardData NonStandardParameter
    } OPTIONAL,
    ...
  }

  Procedure ::= ENUMERATED
  {
    cfu(0), 
    cfb(1),
    cfnr (2),
    ...
  }

  SubscriptionOption ::= ENUMERATED
  {
    noNotification(0),
    notificationWithoutDivertedToNr(1),
    notificationWithDivertedToNr(2),
    ...
  }

  CallDiversionErrors ::= ENUMERATED
  {
    invalidDivertedNumber(12),
    specialServiceNumber(14),
    diversionToServedUserNumber(15),
    numberOfDiversionsExceeded(24),
    temporarilyUnavailable(1000),
    notAuthorized(1007),
    unspecified(1008)
  }

  BasicService ::= ENUMERATED
  {	
    allServices(0),	
    -- speech (1),	
    -- unrestricedDigitalInformation (2),	
    -- audio3.1KHz (3),	
    -- telephony (32),	
    -- teletex (33),	
    -- telefaxGroup4Class1 (34),	
    -- videotexSyntaxBased (35),	
    -- videotelephony (36), 
    ...
  }
  
   DivertingLegInfo2Arg ::= SEQUENCE
                          --  sent from the re-routing h.323-endpoint to the diverted-to h.323-endpoint 
  {
    diversionCounter INTEGER (1..15),
    diversionReason         DiversionReason,
    originalDiversionReason DiversionReason OPTIONAL,
    divertingNr             EndpointAddress OPTIONAL,
    originalCalledNr        EndpointAddress OPTIONAL,
    redirectingInfo         BMPString (SIZE(1..128)) OPTIONAL,
    originalCalledInfo      BMPString (SIZE(1..128)) OPTIONAL,
    extension               CHOICE 
        {
         extensionSeq    ExtensionSeq,        
         nonStandardData NonStandardParameter
        } OPTIONAL,
        ...
 }
  
	                  -- The divertingNr element is mandatory except in the case of interworking
	
   
	
  -- For multimedia calls the value "allServices" shall be used only. 
  -- The usage of the other codepoints for multimedia calls is for further study.

  ExtensionSeq ::= SEQUENCE OF Extension

END -- of Call-Diversion-Operations
